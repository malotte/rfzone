// ---- BEGIN COPYRIGHT -------------------------------------------------------
//
//
// ---- END COPYRIGHT ---------------------------------------------------------
module rfzone
{

    namespace "http://rfzone.com/rfzone";
    prefix rfzone;

    // Import the standard RPC set and its definitions.
    import exosense {
        prefix exo;
    }

    description "Schema for rfzone device management";

    typedef on-off {
      description "On/Off.";
      type enumeration {
	enum on {
	  description "Item is on.";
          value 1;
	}
	enum off {
	  description "Item is off.";
          value 0;
	}
      }
    }

    rpc digital-output {
      description "Turn On/Off.";
      input {
        uses exo:std-request;

	leaf item-id {
	  type uint32;
	}
	leaf channel {
	  type uint32;
	}
	leaf action {
          type on-off;
	}
      }
      // Output only contains status.
      output {
        description
          "Output sent in response to a digital output request";
        
        uses exo:std-callback;
      }
    }

    rpc do {
      description "Turn On/Off.";
      input {
        uses exo:std-request;

	leaf id {
	  type uint32;
	}
	leaf ch {
	  type uint32;
	}
	leaf act {
          type on-off;
	}
      }
      // Output only contains status.
      output {
        description
          "Output sent in response to a digital output request";
        
        uses exo:std-callback;
      }
    }

    rpc gpio-interrupt {
        description "Handle gpio interrupt.";
	input {
          uses exo:std-request;
          
          leaf pin-register {
                description
                "Pin register where interrupt occured.";
		type uint32;
            }
            leaf pin {
              description
                "Pin where interrupt occured.";
              type uint32;
            }
            leaf value {
                description
                "Interrupt value.";
		type uint32;
            }
	}

	output {
            leaf result {
		type exo:status-code;
	    }
	}
    }

    rpc piface-interrupt {
        description "Handle piface interrupt.";
	input {
          uses exo:std-request;
          
            leaf pin {
              description
                "Pin where interrupt occured.";
              type uint32;
            }
            leaf value {
                description
                "Interrupt value.";
		type uint32;
            }
	}

	output {
            leaf result {
		type exo:status-code;
	    }
	}
    }
}
